T2MI-PPS-MIB DEFINITIONS ::= BEGIN

IMPORTS
    MODULE-IDENTITY, OBJECT-TYPE, Integer32, enterprises
        FROM SNMPv2-SMI
    MODULE-COMPLIANCE, OBJECT-GROUP
        FROM SNMPv2-CONF;

t2miPpsMIB MODULE-IDENTITY
    LAST-UPDATED "202401010000Z"
    ORGANIZATION "T2MI PPS Generator Project"
    CONTACT-INFO
        "Email: admin@t2mi-pps.local"
    DESCRIPTION
        "MIB модуль для мониторинга генератора T2MI PPS"
    REVISION "202401010000Z"
    DESCRIPTION
        "Начальная версия"
    ::= { enterprises 99999 }

-- Основные ветви
t2miPpsObjects OBJECT IDENTIFIER ::= { t2miPpsMIB 1 }
t2miPpsConformance OBJECT IDENTIFIER ::= { t2miPpsMIB 2 }

-- Объекты статуса
systemStatus OBJECT-TYPE
    SYNTAX      Integer32 (0..2)
    MAX-ACCESS  read-only
    STATUS      current
    DESCRIPTION
        "Статус системы: 0=оффлайн, 1=онлайн, 2=ошибка"
    ::= { t2miPpsObjects 1 }

ppsCount OBJECT-TYPE
    SYNTAX      Integer32
    MAX-ACCESS  read-only
    STATUS      current
    DESCRIPTION
        "Общее количество сгенерированных импульсов PPS"
    ::= { t2miPpsObjects 2 }

syncStatus OBJECT-TYPE
    SYNTAX      Integer32 (0..1)
    MAX-ACCESS  read-only
    STATUS      current
    DESCRIPTION
        "Статус синхронизации: 0=не синхронизирован, 1=синхронизирован"
    ::= { t2miPpsObjects 3 }

frequencyError OBJECT-TYPE
    SYNTAX      Integer32
    MAX-ACCESS  read-only
    STATUS      current
    DESCRIPTION
        "Частотная ошибка в частях на миллиард (ppb)"
    ::= { t2miPpsObjects 4 }

phaseError OBJECT-TYPE
    SYNTAX      Integer32
    MAX-ACCESS  read-only
    STATUS      current
    DESCRIPTION
        "Фазовая ошибка в наносекундах"
    ::= { t2miPpsObjects 5 }

temperature OBJECT-TYPE
    SYNTAX      Integer32
    MAX-ACCESS  read-only
    STATUS      current
    DESCRIPTION
        "Температура в градусах Цельсия * 100"
    ::= { t2miPpsObjects 6 }

uptime OBJECT-TYPE
    SYNTAX      Integer32
    MAX-ACCESS  read-only
    STATUS      current
    DESCRIPTION
        "Время работы системы в секундах"
    ::= { t2miPpsObjects 7 }

lastSyncTime OBJECT-TYPE
    SYNTAX      Integer32
    MAX-ACCESS  read-only
    STATUS      current
    DESCRIPTION
        "Временная метка последней успешной синхронизации"
    ::= { t2miPpsObjects 8 }

t2miPackets OBJECT-TYPE
    SYNTAX      Integer32
    MAX-ACCESS  read-only
    STATUS      current
    DESCRIPTION
        "Количество полученных пакетов T2MI"
    ::= { t2miPpsObjects 9 }

errorCount OBJECT-TYPE
    SYNTAX      Integer32
    MAX-ACCESS  read-only
    STATUS      current
    DESCRIPTION
        "Общее количество ошибок"
    ::= { t2miPpsObjects 10 }

allanDeviation OBJECT-TYPE
    SYNTAX      Integer32
    MAX-ACCESS  read-only
    STATUS      current
    DESCRIPTION
        "Девиация Аллана * 1e12"
    ::= { t2miPpsObjects 11 }

mtie OBJECT-TYPE
    SYNTAX      Integer32
    MAX-ACCESS  read-only
    STATUS      current
    DESCRIPTION
        "Максимальная ошибка временного интервала (MTIE) в наносекундах"
    ::= { t2miPpsObjects 12 }

gnssStatus OBJECT-TYPE
    SYNTAX      Integer32 (0..2)
    MAX-ACCESS  read-only
    STATUS      current
    DESCRIPTION
        "Статус GNSS: 0=нет фиксации, 1=2D фиксация, 2=3D фиксация"
    ::= { t2miPpsObjects 13 }

holdoverStatus OBJECT-TYPE
    SYNTAX      Integer32 (0..1)
    MAX-ACCESS  read-only
    STATUS      current
    DESCRIPTION
        "Статус удержания: 0=нормальная работа, 1=в режиме удержания"
    ::= { t2miPpsObjects 14 }

dpllLock OBJECT-TYPE
    SYNTAX      Integer32 (0..1)
    MAX-ACCESS  read-only
    STATUS      current
    DESCRIPTION
        "Статус захвата DPLL: 0=не захвачен, 1=захвачен"
    ::= { t2miPpsObjects 15 }

-- Информация о соответствии
t2miPpsCompliances OBJECT IDENTIFIER ::= { t2miPpsConformance 1 }
t2miPpsGroups OBJECT IDENTIFIER ::= { t2miPpsConformance 2 }

-- Заявление о соответствии
t2miPpsCompliance MODULE-COMPLIANCE
    STATUS      current
    DESCRIPTION
        "Заявление о соответствии для генератора T2MI PPS"
    MODULE      -- this module
        MANDATORY-GROUPS { t2miPpsStatusGroup }
    ::= { t2miPpsCompliances 1 }

-- Группы объектов
t2miPpsStatusGroup OBJECT-GROUP
    OBJECTS {
        systemStatus,
        ppsCount,
        syncStatus,
        frequencyError,
        phaseError,
        temperature,
        uptime,
        lastSyncTime,
        t2miPackets,
        errorCount,
        allanDeviation,
        mtie,
        gnssStatus,
        holdoverStatus,
        dpllLock
    }
    STATUS      current
    DESCRIPTION
        "Объекты статуса для генератора T2MI PPS"
    ::= { t2miPpsGroups 1 }

END
